(defun c:test_lb()
	(setq dcl_id(load_dialog "lbtest.dcl"))
	(if (not (new_dialog "lbtest" dcl_id))
		(exit)
	)
	(start_list "blocks")
	(mapcar 'add_list (bnames))
	(end_list)
	(action_tile "accept" "(done_dialog)")
	(start_dialog)
	(unload_dialog dcl_id)
	(princ)
)
(defun c:test_dcl1()
	(setq dcl_id(load_dialog "test.dcl"))
	(if (not (new_dialog "test" dcl_id))
		(exit)
	)
	(action_tile "accept" "(done_dialog)")
	(start_dialog)
	(unload_dialog dcl_id)
	(princ)
)
(defun c:test_dcl2()
	(setq dcl_id(load_dialog "test2.dcl"))
	(if (not (new_dialog "test2" dcl_id))
		(exit)
	)
	(set_tile "name" "Enter Name Here")
	(mode_tile "name" 2)
	(action_tile "name" "(setq name $value)")
	(action_tile "age" "(setq age $value)")
	(action_tile "accept" "(val1)")
	(start_dialog)
	(unload_dialog dcl_id)
	(alert (strcat "Your name is " name 
				 "\n and you are " age " years of age"))
	(princ)
)
(defun val1()
	(if (= (get_tile "name") "Enter Name Here")
		(progn
			(set_tile "error" "You must enter a name!")
			(mode_tile "name" 2)
		)
		(val2)
	)
)
(defun val2()
	(if(< (atoi (get_tile "age")) 1)
		(progn
			(set_tile "error" "Invalid age - please try again!!")
			(mode_tile "age" 2)
		);progn
		(done_dialog)
	);if
);defun
