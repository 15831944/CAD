(defun c:data()
	(getdata)
)

(defun getdata()
	(setq d(entget(car(entsel "specify the entity:"))))
)

(defun setvar0()
	(setq cmho(getvar "CMDECHO"))
	(setq hiht(getvar "HIGHLIGHT"))
	(setq blde(getvar "BLIPMODE"))
	;(setq snde(getvar "SNAPMODE"))
	(setq osde(getvar "OSMODE"))
	;(setq pist(getvar "PICKFIRST"))
	(setvar "CMDECHO" 0)
	(setvar "HIGHLIGHT" 0)
	(setvar "BLIPMODE" 0)
	(setvar "SNAPMODE" 0)
	(setvar "OSMODE" 0)
)
(defun resetvar0()
	(setvar "CMDECHO" cmho)
	(setvar "HIGHLIGHT" hiht)
	(setvar "BLIPMODE" blde)
	;(setvar "SNAPMODE" snde)
	(setvar "OSMODE" osde)
	;(setvar "PICKFIRST" pist)
)

(defun c:printe()
	(setq elist(getdata))
	(foreach e elist
		(print e)
	)
)

(defun c:findcircles(/ en ed obj)
	(terpri)
	(princ "center point                   Radius")
	(terpri)
	(setq en(entnext))
	(while en 
		(setq ed(entget en))
		(if(eq (cdr(assoc 0 ed) "CIRCLE"))
			(progn
				(setq obj(print (cdr(assoc 10 ed ))))
				(princ(tab obj 34))
				(prin1 (cdr(assoc 40 ed)))
			)
			(setq en(entnext en ))
		)
	)
	(prin1)
)

(defun c:long-dist(/ tot-dist cnt p1 p2)
	(initget 1)
	(setq tot-dist 0.0 
		cnt 0 
		p1(getpoint "starting point:")
	)
	(while (setq p2(getpoint "\n next point:"))
		(princ "distance:")
		(setq tot-dist(+ tot-dist (prin1 (distance p1 p2)))
			cnt(1+ cnt)
			p1 p2)
	)
	(and (> cnt 0)
		(princ "\n total distance:")
		(prin1 tot-dist)
		(princ "average:")
		(prin1(/ tot-dist cnt))
	)
	(prin1)
)


(defun c:lst()
	(foreach x '(a b c)
		(print x )
	)
)
(defun guanxian(pt rad)
	(setvar0)	
	(command "layer" "S" "中实线" "")
	(command "CIRCLE" pt rad)
	;(vl-cmdf "CIRCLE" pt (* rad 1.1))
	;(setq rad2(* 1.1 rad))
	(command "CIRCLE" pt (* rad 1.1))
	(setq pt1(polar pt 0 (* 1.2 rad)))
	(setq pt2(polar pt (/ pi 2) (* 1.2 rad)))
	(setq pt3(polar pt (- pi) (* 1.2 rad)))
	(setq pt4 (polar pt (-(/ pi 2)) (* 1.2 rad)))
	;(command ".LINE" pt1 pt3 "")
	;(command ".LINE" pt2 pt4 "")
	(command "layer" "S" "点划线" "")
	(vl-cmdf "line" pt1 pt3 "")
	(vl-cmdf "line" pt2 pt4 "")
	(princ)
	(resetvar0)
)

(defun c:txtLine()
	(setq ent(car(entsel "specify a text to line:")))
	(setq elist(entget ent))
	(if (eq (cdr(assoc 0 elist)) "TEXT")
		(progn
			(setvar0)
			(setq lay(getvar "clayer"))
			(setq th(cdr(assoc 40 elist)))；字高
			(command "ucs" "entity" ent);这个命令含义是什么还未搞清楚，但是很有效
			;(setq tang(cdr(assoc 50 elist)))
			(setq ptlist(textbox elist))；左下角右上角点位list
			(setq pt1(car ptlist))；左下角
			(setq pt2(cadr ptlist))；右上角
			(setq pt1x(polar pt1 (-  pi) (* 0.1 th)))
			(setq pt2x(list (car pt2) (cadr pt1) (caddr pt2)))
			(setq pt2x(polar pt2x 0 (* 0.1 th)))
			(setq pt1x(polar pt1x (- (/ pi 2)) (* 0.15 th)))
			(setq pt2x(polar pt2x (- (/ pi 2)) (* 0.15 th)))
			(command "layer" "s" "中实线" "")
			(command "PLINE" pt1x "w" (* 0.1 th) "" pt2x  "")
			(setq pt1x(polar pt1x (- (/ pi 2)) (* 0.2 th)))
			(setq pt2x(polar pt2x (- (/ pi 2)) (* 0.2 th)))
			(command "line" pt1x pt2x "")
			(resetvar0)
			(setvar "CLAYER" lay)
		)
		(princ "No text is selected!")
	)
)

(defun c:laytxtline();当前图层text全部划线
	(setq ss(ssget "x" (list (cons 8 (getvar "CLAYER")) (cons 0 "TEXT"))))
	(setq i 0 )
	(setvar0)
	(setq lay(getvar "CLAYER"))
	(repeat (sslength ss)
		(progn
			(setq ssi(ssname ss i))
			(setq elist(entget ssi))
			(setq th(cdr(assoc 40 elist)))；字高
			(command "ucs" "entity" ssi);这个命令含义是什么还未搞清楚，但是很有效
			;(setq tang(cdr(assoc 50 elist)))
			(setq ptlist(textbox elist))；左下角右上角点位list
			(setq pt1(car ptlist))；左下角
			(setq pt2(cadr ptlist))；右上角
			(setq pt1x(polar pt1 (-  pi) (* 0.1 th)))
			(setq pt2x(list (car pt2) (cadr pt1) (caddr pt2)))
			(setq pt2x(polar pt2x 0 (* 0.1 th)))
			(setq pt1x(polar pt1x (- (/ pi 2)) (* 0.15 th)))
			(setq pt2x(polar pt2x (- (/ pi 2)) (* 0.15 th)))
			(command "layer" "s" "中实线" "")
			(command "PLINE" pt1x "w" (* 0.1 th) "" pt2x  "")
			(setq pt1x(polar pt1x (- (/ pi 2)) (* 0.2 th)))
			(setq pt2x(polar pt2x (- (/ pi 2)) (* 0.2 th)))
			(command "line" pt1x pt2x "")
			(setq i(1+ i))
		)
	)
	(resetvar0)
	(setvar "CLAYER" lay)
)
