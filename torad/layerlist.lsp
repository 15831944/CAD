(defun c:layerlist()
	;;;	(setq layerlst (tblnext "layer" T))
	;;;(if (and (< 0 (cdr(assoc 62 layerlst)) )
	;;;;	(= 0 (logand 1 (cdr(assoc 70 layerlst))))	
	;;;)
	;;;(setq layerlst (cons (cdr(assoc 2 layerlst)) layerlst))
	
  ;;;)
	;;;layerlst
	(setq layerlist(tblnext "layer" T))
	(if (and (< 0 (cdr (assoc 62 layerlist) ))
				(= 0 (logand 1 (cdr(assoc 70 layerlist)))))
		(setq layerlist(list (cdr(assoc 2 layerlist))))
	)
	(while(setq layer(tblnext "layer"))
		(if(and (< 0 (cdr (assoc 62 layer)))
				 (= 0 (logand 1 (cdr(assoc 70 layer)))))
			(setq layerlist(cons (cdr (assoc 2 layer )) layerlist))
		)
	)
	layerlist
)

(defun c:blocklist()
	(setq blocklist(tblnext "block" T))
	;(if (and (< 0 (cdr (assoc 62 blocklist)))
	;			(= 0 (logand 1 (cdr (assoc 70 blocklist))))				
	;		)
	;	(setq blocklist(list(cdr (assoc 2 blocklist))))
	;)
	;(while(setq blist(tblnext "block"))
	;	(if(and (< 0 (cdr(assoc 62 blist)))
	;			 (= 0 (logand 1 (cdr (assoc 70 blist))))	 
	;		 )
	;		(setq blocklist(cons (cdr (assoc 2 blist)) blocklist))
	;	)
	;)
	(if (= 1 (logand 1 (cdr(assoc 70 blocklist))))
		(setq blocklist(list (cdr (aasoc 2 blocklist))))	
		(setq blocklist nil)
	)
	(while(setq blist(tblnext "block"))
		(if(= 1 (logand 1 (cdr(assoc 70 blist))))
			(setq blocklist(cons (cdr(assoc 2 blist)) blocklist))
		)
	)
	blocklist
)
