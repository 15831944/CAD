(defun c:tbox(/ en tb)
	(setq en(car(entsel "specify the text:")))
	(command "ucs" "entity" en)
	(setq tb(textbox(entget en)))
	(boxit (car tb) (cadr tb) en)
	(command "ucs" "p")
	(princ)
)
(defun boxit(p1 p2 en / off)
	(setq p1(trans p1 1 en)
		p2(trans p2 1 en)
	)
	(setq off(getdist "\n Enter offset for border: "))
	(entmake (list (cons 0 "polyline") (cons 70 1)))
	(entmake (list (cons 0 "vertex") (list 10 (- (car p1) off) (- (cadr p1) off))))
	(entmake (list (cons 0 "vertex") (list 10 (- (car p1) off) (+ (cadr p2) off))))
	(entmake (list (cons 0 "vertex") (list 10 (+ (car p2) off) (+ (cadr p2) off))))
	(entmake (list (cons 0 "vertex") (list 10 (+ (car p2) off) (- (cadr p1) off))))
	(entmake '((0 . "seqend")))
)
